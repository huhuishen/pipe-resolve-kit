(defun psk-comp-getname	(comp /)
  (p-get comp ".CLASS")
)

(defun psk-comp-gettype	(comp /)
  (p-get comp ".TYPE")
)

(defun psk-comp-getename (comp /)
  (p-get comp -1)
)

;; (psk-comp-save '(("CLASS" . "PATH") ("TYPE" . "RECTANGULAR") ("SERV" . "OA") ("W" . 500) ("H" . 320)) (car (entsel)) "PSK-COMP")
(defun psk-comp-save (comp ename appid /)
  (if ename
    (p-xprop-set ename appid comp)
  )
)
;;

;; (psk-comp-load (car (entsel)) )
;; ((-1 . <图元名: 7ff47770d020>) ("CLASS" . "PATH") ("TYPE" . "RECTANGULAR") ("SERV" . "OA") ("W" . 500) ("H" . 320))
(defun psk-comp-load (ename  / props)
  (if (setq props (p-xprop-getall ename "PSK-PATH,PSK-COMP,PSK-BLOCK"))
    (cons (cons -1 ename) props)
    nil ;_相应的appid不存在时 ，不生成对象
  )
)


;;;(defun psk-comp-getports (comp / name)
(defun psk-comp-set (en prop)
  (if (p-xdata-get en "PSK-COMP")
    (p-xprop-set en "PSK-COMP" prop)
    (if	(p-xdata-get en "PSK-BLOCK")
      (psk-key-set en prop)
      (p-xprop-set en "PSK-PATH" prop)
    )
  )
)

(defun psk-comp-get (en keys)
  (if (p-xdata-get en "PSK-COMP")
    (p-xprop-get en "PSK-COMP" keys)
    (p-xprop-get en "PSK-PATH" keys)
  )
)
;;;)
(defun psk-comp-getports (comp / name)
;;;  (if (/= 'ename (type comp))
;;;    (progn
;;;      (setq name (psk-comp-getname comp))
;;;      (cond
;;;	((= "FIT" name)
;;;	 (psk-fit-getports comp)
;;;	)
;;;	((= "PATH" name)
;;;	 (psk-path-getports comp)
;;;	)
;;;      )
;;;    )
;;;    (if	(p-xdata-get comp "PSK-PATH")
;;;      (psk-path-getports comp)
;;;      (if (p-xdata-get comp "PSK-COMP")
;;;	(psk-fit-getports comp)
;;;      )
;;;    )
;;;  )
  (if (/= 'ename (type comp))
    (setq comp (psk-comp-getename comp))
  )
  (if (p-xdata-get comp "PSK-PORT")
    (psk-fit-getports comp)
    (psk-path-getports comp)
  )
)
(defun psk-comp-moveport (comp p newp /)
  (setq name (psk-comp-getname comp))
  (cond
    ((= "FIT" name)
     (psk-fit-moveport comp p newp)
    )
    ((= "PATH" name)
     (psk-path-moveport comp p newp t)
    )
  )
)
;;; (psk-comps-moveport (setq p (getpoint)) (getpoint p) (psk-comps-buildbst (psk-comps-all) 0.1) nil)
(defun psk-comps-moveport (p newp bst moved /)
  (if (null moved)
    (setq moved (ssadd))
  )
  (foreach comp	(p-bst-find p bst 0.1)
    (if	(not (ssmemb (p-get comp -1) moved))
      (progn
	(setq r	    (psk-comp-moveport comp p newp)
	      moved (ssadd (p-get comp -1) moved)
	)
	(if r
	  (progn
;;;	    (princ r)
	    (setq offset (car r)
		  r	 (cdr r)
	    )
	    (foreach p	r
	      (psk-comps-moveport p (mapcar '+ p offset) bst moved)
	    )
	  )
	)
      )
    )
  )
)
;;


(defun psk-ss->comps (ss)
  (mapcar 'psk-comp-load (p-ss->enames ss))
)
(defun psk-comps-ssget ()
  (psk-ss->comps (ssget '((-3 ("PSK-PATH,PSK-COMP,PSK-BLOCK")))))
)
(defun psk-comps-all ()
  (psk-ss->comps (ssget "X" '((-3 ("PSK-PATH,PSK-COMP,PSK-BLOCK")))))
)
(defun psk-comps-fromwindow (p1 p2)
  (psk-ss->comps (ssget "W" p1 p2 '((-3 ("PSK-PATH,PSK-COMP,PSK-BLOCK")))))
)
(defun psk-comps-fromviewport ()
  (psk-comps-fromwindow
    (trans (getvar "EXTMIN") 0 1)
    (trans (getvar "EXTMAX") 0 1)
  )
)
