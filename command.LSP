(defun c:ar ()
  (p-commandrun '(psk-editor-createpath))
)
(defun c:cx ()
  (p-commandrun '(psk-comps-modify))
)

(defun c:dc ()
  (p-commandrun '(psk-paths-connect (psk-paths-pick 4) t))
)

(defun c:pskconfig ()
  (p-commandrun '(psk-settings-change))
)

(defun c:dr (/)
  (p-commandrun '(psk-cmd-redraw))
)

(defun c:bz ()
  (p-commandrun '(psk-cmd-iden))
)
(defun c:bom ()
  (p-commandrun '(psk-comps-getbom (psk-comps-ssget)))
)

(defun c:showbranchs ()
  (p-commandrun '(psk-show-branchs (getpoint "指定总管口")))
)

(setq $psk-last-flr 500.)
(defun c:sumbranchs ()
  (p-commandrun '(psk-path-sum (psk-comp-buildmap (getpoint)) (p-edit-value "输入末端流量" $psk-last-flr)))
)

(defun movepath	(resize / en pf pt)
  (if (and (setq en (car (entsel)))
	   (setq pf (trans (getpoint "指定管口") 1 0))
	   (setq pt (trans (getpoint pf "指定管口的新位置") 1 0))
      )
    (progn
      (psk-path-moveport en pf pt resize)
      (psk-comp-redraw (psk-comp-load en))
    )
  )
)
(defun c:movepath ()
  (p-commandrun '(movepath nil))
)
(defun c:movepathresize	()
  (p-commandrun '(movepath t))
)

(defun c:pskabout ()
  (alert (strcat $psk-about "\n\n小而强大"))
  (princ)
)
